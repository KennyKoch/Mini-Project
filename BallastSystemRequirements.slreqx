# BallastSystemRequirements

## REQ-001: Draft and Trim Adjustment (Functional)
The vessel shall capable of changining its draft and trim
- Rationale: The vessel must be able to safely travel underneath low bridges and navigate shallow habors/channels

### REQ-002: Draft (Functional)
The vessel shall be capable of changing its draft between 10.0 and 25.0 feet

### REQ-003: Trim (Functional)
The vessel shall be capable of altering its trim by the stern between +5.0 feet and -5.0 feet

## REQ-004: Deballasting Duration (Functional)
The ballast system shall be capable of deballasting a 100% full system in 12.0 hours
- Rationale: Minimize time waiting for deballasing operations

### REQ-005: Wing Tank Deballasting (Functional)
The ballast system shall be capable of deballasting the main wing tanks within 4.0 hours

### REQ-006: Aft Peak Tank Deballasting (Functional)
The ballast system shall be able to deballast the aft peak tank in 2.0 hours

### REQ-007: Fore Peak Tank (Functional)
The ballast system shall be capable of deballasting the for peak tank in 1.5 hours

## REQ-008: Pumping Redundancy (Functional)
The ballasy system shall have redundant pumping capacity such that a single pump failure does not reduce total flow capacity by more than 50%
- Rationale: Adds redundancy to prevent a single point of failure for the system

## DER-REQ-009: [DERIVED} Pumping Flow Rate (Functional)
Derived from tank sizing and time requirements. The ballast pumps shall provide a volumetric flowrate of 5000 gal/hr

## REQ-010: Piping Material (Functional)
All ballast system piping shall be conrtucted from 70/30 CuNi alloy
- Rationale: Ballast water can cause corrosion of piping

## ASM-001: [ASSUMPTION] Design Harbor Depth (Informational)
The minimum harbor depth for ballasting operations is 35.0 feet to pervent silt from entering sea chests
